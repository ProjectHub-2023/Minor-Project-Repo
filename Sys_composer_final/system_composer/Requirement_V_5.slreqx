# Requirement_V_5

## Requirement_V_5: References to Requirement_V_5.docx (Container)
Read-only references to Microsoft Word document.

### F1 Detect (Functional)

### F1.1 When <input ‘System Ready’: F1.1 When <input ‘System Ready’ ... (Functional)
F1.1 When <input ‘System Ready’ is received >the function <F1.1> shall generate <output ‘SystemCalibrated’ >.

### F1.2 When <input ‘SystemCalibrat: F1.2 When <input ‘SystemCalibrat... (Functional)
F1.2 When <input ‘SystemCalibrated’ is received, input ‘LookForProduct’ is received

### AND input ‘Reset Signal’ is rece: AND input ‘Reset Signal’ is rece... (Functional)
AND input ‘Reset Signal’ is received the function <F1.2> shall generate <output ‘InterpretSignal’ >.

### F1.3 When <input ‘InterpretSigna: F1.3 When <input ‘InterpretSigna... (Functional)
F1.3 When <input ‘InterpretSignal’ is received AND input ‘Product’ is received>the function <F1.3> shall generate <output ‘Product Detected’ AND ’Count’>.

### F2 Inspect (Functional)

### F2.1 When <input: ‘Product’>, Th: F2.1 When <input: ‘Product’>, Th... (Functional)
F2.1 When <input: ‘Product’>, The function<F2.1>Shall generate <output: ‘OutBus’>

### F2.2 When <input: ‘Detection sig: F2.2 When <input: ‘Detection sig... (Functional)
F2.2 When <input: ‘Detection signal’>, The function<F2.2>Shall generate <output: ‘Trigger’>

### F2.3 When <input: ‘Product AND P: F2.3 When <input: ‘Product AND P... (Functional)
F2.3 When <input: ‘Product AND Power AND Trigger’>, The function<F2.3>Shall generate <output: ‘Product Image AND OutBus AND OutBus1’>

### F2.4 When <input: ‘Product Image: F2.4 When <input: ‘Product Image... (Functional)
F2.4 When <input: ‘Product Image’>, The function<F2.4>Shall generate <output: ‘ProductOrientation’>

### F2.5 When <input: ‘Product Image: F2.5 When <input: ‘Product Image... (Functional)
F2.5 When <input: ‘Product Image’>, The function<F2.5>Shall generate <output: ‘ExtractedQRCode’>

### F2.6 When <input: ‘ExtractedQRCo: F2.6 When <input: ‘ExtractedQRCo... (Functional)
F2.6 When <input: ‘ExtractedQRCode’>, The function<F2.6>Shall generate <output: ‘ExportQR’>

### F2.7 When <input: ‘Product Image: F2.7 When <input: ‘Product Image... (Functional)
F2.7 When <input: ‘Product Image’>, The function<F2.7>Shall generate <output: ‘Dimension of product’>

### F2.7.1 When <input: ‘Product Ima: F2.7.1 When <input: ‘Product Ima... (Functional)
F2.7.1 When <input: ‘Product Image’>, The function<F2.7.1>Shall generate <output: ‘Coordinates’>

### F2.7.2 When <input: ‘Coordinates: F2.7.2 When <input: ‘Coordinates... (Functional)
F2.7.2 When <input: ‘Coordinates’>, The function<F2.7.2>Shall generate <output: ‘Dimension of product’>

### F2.8 When <input: ‘Product Image: F2.8 When <input: ‘Product Image... (Functional)
F2.8 When <input: ‘Product Image’>, The function<F2.7>Shall generate <output: ‘ProductPosition’>

### F3 Compare Dimensions (Functional)

### F3.1 When <input ‘Dimension of p: F3.1 When <input ‘Dimension of p... (Functional)
F3.1 When <input ‘Dimension of product’ is received >the function <F3.1> shall generate <output ‘ImportedDimensions’ >.

### F3.2 When <input ‘ImportedDimens: F3.2 When <input ‘ImportedDimens... (Functional)
F3.2 When <input ‘ImportedDimensions’ is received >the function <F3.2> shall generate <output ‘ReferDBDimensions’ AND ‘CurrentDimensions’>.

### F3.3 When <input ‘ReferDBDimensi: F3.3 When <input ‘ReferDBDimensi... (Functional)
F3.3 When <input ‘ReferDBDimensions’ is received >the function <F3.3> shall generate <output ‘DBDimensions’ >.

### F3.4 When <input ‘DBDimensions’: F3.4 When <input ‘DBDimensions’ ... (Functional)
F3.4 When <input ‘DBDimensions’ is received >the function <F3.4> shall generate <output ‘ExpectedDimensions’ >.

### F3.5 When <input ‘ExpectedDimens: F3.5 When <input ‘ExpectedDimens... (Functional)
F3.5 When <input ‘ExpectedDimensions’ is received AND input ‘CurrentDimensions’ is received >the function <F3.5> shall generate <output ‘Faulty Product Detected’ AND ‘BeginPickOperation’>.

### F4 Calibrate (Functional)

### F4.1 When <input: ‘Power AND Mot: F4.1 When <input: ‘Power AND Mot... (Functional)
F4.1 When <input: ‘Power AND Motor AND Frame components’>, The function<F4.1>Shall generate <output: ‘ConfirmSetup’>.

### F4.1.1 When <input: ‘Frame compo: F4.1.1 When <input: ‘Frame compo... (Functional)
F4.1.1 When <input: ‘Frame components’>, The function<F4.1.1>Shall generate <output: ‘Frame’>.

### F4.1.2 When <input: ‘Motor AND F: F4.1.2 When <input: ‘Motor AND F... (Functional)
F4.1.2 When <input: ‘Motor AND Frame’>, The function<F4.1.2>Shall generate <output: ‘Frame and motor setup’>.

### F4.1.3 When <input: ‘Frame and m: F4.1.3 When <input: ‘Frame and m... (Functional)
F4.1.3 When <input: ‘Frame and motor setup AND Power’>, The function<F4.1.3>Shall generate <output: ‘Physical setup -> ConfirmSetup’>.

### F4.2 When <input: ‘UIReady’>, Th: F4.2 When <input: ‘UIReady’>, Th... (Functional)
F4.2 When <input: ‘UIReady’>, The function<F4.2>Shall generate <output: ‘Trigger’>.

### F4.3 When <input: ‘Trigger AND S: F4.3 When <input: ‘Trigger AND S... (Functional)
F4.3 When <input: ‘Trigger AND SetupConfirmation AND Power’>, The function<F4.3>Shall generate <output: ‘JogComplete’>.

### F4.4 When <input: ‘JogComplete A: F4.4 When <input: ‘JogComplete A... (Functional)
F4.4 When <input: ‘JogComplete AND Power’>, The function<F4.4>Shall generate <output: ‘Robot at home position -> ConfirmCalibration’>.

### F5 Pick Product (Functional)

### F Begin Task When <input: ‘Beigi: F Begin Task When <input: ‘Beigi... (Functional)
F Begin Task When <input: ‘Beiginpickoperation’>, The function<F Begin Task>Shall generate <output: ‘Coordintes AND Orientation’>.

### F5.1 When <input: ‘Coordinates’>: F5.1 When <input: ‘Coordinates’>... (Functional)
F5.1 When <input: ‘Coordinates’>, The function<F5.1>Shall generate <output: ‘Importedcoordiantes’>.

### F5.2 When <input: ‘Orientation’>: F5.2 When <input: ‘Orientation’>... (Functional)
F5.2 When <input: ‘Orientation’>, The function<F5.2>Shall generate <output: ‘Importedorientation’>.

### F5.3 When <input: ‘Importedorien: F5.3 When <input: ‘Importedorien... (Functional)
F5.3 When <input: ‘Importedorientation AND Importedcoordinates AND New coordinates ’>, The function<F5.3>Shall generate <output: ‘Current Position AND Defined Path’>.

### F5.4 When <input: ‘Corrected Pos: F5.4 When <input: ‘Corrected Pos... (Functional)
F5.4 When <input: ‘Corrected Postition AND Corrected Force’>, The function<F5.4>Shall generate <output: ‘New coordinates AND New Force value’>.

### F5.5 When <input: ‘Defined Path’: F5.5 When <input: ‘Defined Path’... (Functional)
F5.5 When <input: ‘Defined Path’>, The function<F5.5>Shall generate <output: ‘Ready to pick Pick Product’>.

### F5.6 When <input: ‘New Force val: F5.6 When <input: ‘New Force val... (Functional)
F5.6 When <input: ‘New Force value AND Ready to pick Pick Product ’>, The function<F5.6>Shall generate <output: ‘Product Picked AND Current Force’>

### F6 Translate Product (Functional)

### F6.1 When <input ‘Product Picked: F6.1 When <input ‘Product Picked... (Functional)
F6.1 When <input ‘Product Picked’ is received >the function <F6.1> shall generate <output ‘Ready to be Placed’ >.

### F7 Place Product (Functional)

### F7.1 When <input ‘Corrected Posi: F7.1 When <input ‘Corrected Posi... (Functional)
F7.1 When <input ‘Corrected Position’ is received >the function <F7.1> shall generate <output ‘New Position’ >.

### F7.2 When <input ‘Ready to be pl: F7.2 When <input ‘Ready to be pl... (Functional)
F7.2 When <input ‘Ready to be placed’ is received AND input ‘New Position’ is received>the function <F1.3> shall generate <output ‘Gripper Lowered’ >.

### F7.3 When <input ‘Gripper Lowere: F7.3 When <input ‘Gripper Lowere... (Functional)
F7.3 When <input ‘Gripper Lowered’ is received >the function <F7.3> shall generate <output ‘Product Released’ >.

### F7.4 When <input ‘Product Releas: F7.4 When <input ‘Product Releas... (Functional)
F7.4 When <input ‘Product Released’ is received >the function <F7.4> shall generate <output ‘Product Placed’ >.

### F08 Handle Contingencies (Functional)

### F8.1 When <input ‘Force on gripp: F8.1 When <input ‘Force on gripp... (Functional)
F8.1 When <input ‘Force on gripper’ is received >the function <F8.1> shall generate <output ‘Appropriate force’ >.

### F9 Hold Operations (Functional)

### F9.1 When <input ‘Product Not De: F9.1 When <input ‘Product Not De... (Functional)
F9.1 When <input ‘Product Not Detected’ is received >the function <F9.1> shall generate <output ‘Return To Detection’ >.

### F10 Halt Operations (Functional)

### F10.1 When <input ‘EmergencyStop: F10.1 When <input ‘EmergencyStop... (Functional)
F10.1 When <input ‘EmergencyStopSignal’ is received >the function <F10.1> shall generate <output ‘RecievedInput’ >.

### F10.2 When <input ‘RecievedInput: F10.2 When <input ‘RecievedInput... (Functional)
F10.2 When <input ‘RecievedInput’ is received >the function <F10.2> shall generate <output ‘StopOperation’ >.

### F10.3 When <input ‘StopOperation: F10.3 When <input ‘StopOperation... (Functional)
F10.3 When <input ‘StopOperation’ is received >the function <F10.3> shall generate <output ‘Stop Signal’ AND ‘NotifyOperator’>.

### F10.3 When <input ‘NotifyOperato: F10.3 When <input ‘NotifyOperato... (Functional)
F10.3 When <input ‘NotifyOperator’ is received >the function <F10.4> shall generate <output ‘NotifySTOP’ >.

### F11.Handle User Interface (Functional)

### F1.1 When <input ‘Reset Confirma: F1.1 When <input ‘Reset Confirma... (Functional)
F1.1 When <input ‘Reset Confirmation’ is received >the function <F1.1> shall generate <output ‘Logout Successful’ >.

### F11.2 When <input ‘Power Supply’: F11.2 When <input ‘Power Supply’... (Functional)
F11.2 When <input ‘Power Supply’ is received >the function <F11.2> shall generate <output ‘WaitforInput’ >.

### F13.3 When <input ‘Receive User: F13.3 When <input ‘Receive User ... (Functional)
F13.3 When <input ‘Receive User Input’ is received >the function <F11.3> shall generate <output ‘Ready to Interact’ >.

### F11.4 When <input ‘Provide User: F11.4 When <input ‘Provide User ... (Functional)
F11.4 When <input ‘Provide User Interface’ is received >the function <F11.4> shall generate <output ‘VisualsReady’ >.

### F11.5 When <input ‘VisualsReady’: F11.5 When <input ‘VisualsReady’... (Functional)
F11.5 When <input ‘VisualsReady’ and ‘User Credentials’ is received >the function <F11.5> shall generate <output ‘Received Credentials’ >.

### F11.6 When <input ‘Received Cred: F11.6 When <input ‘Received Cred... (Functional)
F11.6 When <input ‘Received Credentials’ is received >the function <F11.6> shall generate <output ‘Confirmation’ >.

### F11.7 When <input ‘Confirmation’: F11.7 When <input ‘Confirmation’... (Functional)
F11.7 When <input ‘Confirmation’ is received >the function <F11.7> shall generate <output ‘Login Confirm’ and ‘Open Dashboard’ >.

### F11.8 When <input ‘Open Dashboar: F11.8 When <input ‘Open Dashboar... (Functional)
F11.8 When <input ‘Open Dashboard’ is received >the function <F11.8> shall generate <output ‘Dashboard Loaded’ >.

### F11.9 When <input ‘Stop Button’: F11.9 When <input ‘Stop Button’ ... (Functional)
F11.9 When <input ‘Stop Button’ is received >the function <F11.9> shall generate <output ‘Notify Emergency’ >.

### F11.10 When <input ‘Dashboard Lo: F11.10 When <input ‘Dashboard Lo... (Functional)
F11.10 When <input ‘Dashboard Loaded’ and ‘Faulty Product Detected’ and ‘Count’ and ‘Observe parameter’ is received > the function <F11.10> shall generate <output ‘Notify Emergency’ >.

### F11.11 When <input ‘Notify Emerg: F11.11 When <input ‘Notify Emerg... (Functional)
F11.11 When <input ‘Notify Emergency’ is received >the function <F11.11> shall generate <output ‘’ >.

### F11.12 When <input ‘Logout Confi: F11.12 When <input ‘Logout Confi... (Functional)
F11.12 When <input ‘Logout Confirmed’ and ‘Stop Confirm’ is received >the function <F11.12> shall generate <output ‘Reset system’ >.

### F11.13 When <input ‘DB Updated’: F11.13 When <input ‘DB Updated’ ... (Functional)
F11.13 When <input ‘DB Updated’ is received >the function <F11.13> shall generate <output ‘Stop Operation’ >.

### F12 Reset Position (Functional)

### F12.1 When <input ‘Product place: F12.1 When <input ‘Product place... (Functional)
F12.1 When <input ‘Product placed’ is received OR ‘Log-out’ is received >the function <F12.1> shall generate <output ‘home position’ >.

### F12.2 When <input ‘home position: F12.2 When <input ‘home position... (Functional)
F12.2 When <input ‘home position’ is received >the function <F12.2> shall generate <output ‘power off signal’ AND ‘Coordinates’ >.

### F12.3 When <input ‘power off sig: F12.3 When <input ‘power off sig... (Functional)
F12.3 When <input ‘power off signal’ is received >the function <F12.3> shall generate <output ‘System ready’ >.

### F12.4 When <input ‘Coordinates’: F12.4 When <input ‘Coordinates’ ... (Functional)
F12.4 When <input ‘Coordinates’ is received >the function <F12.4> shall generate <output ‘HoldAtHomePosition’ >.

## Requirement_V_5_1: References to Requirement_V_5_1.docx (Container)
Imported from Microsoft Word

### F11.14 When <input ‘Logout Promp... (Functional)
F11.14 When <input ‘Logout Prompt’ is received >the function <F11.14> shall generate <output ‘Logout Confirm’ and ‘DB Updated’ >.

### F11.15 When <input ‘Show Paramet... (Functional)
F11.15 When <input ‘Show Parameters’ is received >the function <F11.15> shall generate <output ‘system state’ and ‘Logout Prompt’ and ‘Observe Parameters’>.
